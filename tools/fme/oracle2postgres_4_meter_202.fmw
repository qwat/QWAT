FME workspace oracle2postgres_4_meter_202.fmw

Parameters:
- DestDataset_POSTGIS = sige   # Destination PostGIS Dataset
- SourceDataset_ORACLE8I_DB_3 = orcl   # Source Oracle Non-spatial Service

Readers:
- ORACLE8I_DB_2: ORACLE8I_DB from $(SourceDataset_ORACLE8I_DB_3)

Writers:
- POSTGIS_1: POSTGIS to $(DestDataset_POSTGIS) in EPSG:21781

SIGE_DISTRIBUTION.WA_EINBAUTEIL (reader ORACLE8I_DB_2)
    attributes: ABMESSUNG varchar2(25), ALTITUDE number(5,1), ANTRIEB_MOTOR number(1,0), AREA_NOMINAL number(20,8), ARTIKEL_NR varchar2(50), AUSGANGSDRUCK number(10,5), BEMERKUNG varchar2(255), BESCHICHTUNG_AUSSEN varchar2(5), BESCHICHTUNG_INNEN varchar2(5), BEZEICHNUNG varchar2(50), BEZEICHNUNG2 varchar2(50), DATUM_INBETRIEBNAHME date, DELETED number(1,0), DRUCKZONE_ID number(20,0), EIGENTUMSVERHAELTNIS varchar2(5), EINBAUFIRMA_ID number(10,0), EINBAUJAHR number(20,0), EINBAUORT varchar2(50), EINBAUTEIL_ART varchar2(6), EINGANGSDRUCK number(10,5), F1 varchar2(20), F2 varchar2(80), F3 varchar2(20), FID number(10,0), FID_LAGEBEZEICHNUNG number(10,0), FID_NETZPUNKT number(10,0), FLST_KENNZEICHEN_OF varchar2(25), FLST_NENNER number(20,0), FLST_NR number(20,0), FLST_ZAEHLER number(20,0),
      FOERDERLEISTUNG number(20,8), FOLIO varchar2(15), GEMARKUNG number(20,0), GETRIEBE_NUMMER varchar2(20), GID number(10,0), HAUSNUMMER number(10,0), HAUSNUMMER_ERG varchar2(10), HERSTELLER_ID number(20,0), ID_BESCHILDERUNG number(10,0), ID_DREHRICHTUNG number(10,0), ID_GETRIEBE_HERSTELLER number(10,0), ID_GETRIEBE_TYP number(10,0), ID_MOTOR_HERSTELLER number(10,0), ID_MOTOR_TYP number(10,0), ID_PUMPE_ART number(10,0), INHALT varchar2(10), KATASTERBLATT varchar2(5), LAGEGENAUIGKEIT varchar2(5), MATERIAL varchar2(5), MAX_HUB number(20,8), MOTOR_DREHZAHL number(10,0), MOTOR_LEISTUNG number(10,8), MOTOR_NENNSTROM varchar2(10), MOTOR_NUMMER varchar2(20), MOTOR_SPANNUNG varchar2(15), NAME varchar2(60), NAME2 varchar2(50), NENNDRUCK number(20,5), NENNLEISTUNG number(20,8), NENNSTROM number(20,8),
      NENNWEITE varchar2(10), NENNWEITE2 number(10,5), NENNWEITE3 number(10,5), NENNWEITE4 number(10,5), POINT_NUMBER varchar2(50), PUMPE_RESERVE number(1,0), PUMPE_RESERVE_LAGERORT varchar2(50), PUMPE_TYP varchar2(20), SCHILD_MONTIERT number(1,0), SKALIERFAKTOR number(20,5), STANDORT varchar2(255), STATUS varchar2(5), STRANG_ID number(10,0), TB_POINT_NUMBER number(15,0), UMDREHUNG_MIN number(10,0), VERBINDUNGSART varchar2(15), V_COMMUNE number(10,0), WANDLER_ABFRAGE number(1,0), WANDLER_TYP varchar2(50), ZERTIFIKAT varchar2(10)
    -> AttributeFilter
AttributeFilter
    ATTR_NAME = DELETED
    ATTR_VALUES = 0
    0 -> AttributeFilter_2
AttributeFilter_2
    ATTR_NAME = EINBAUTEIL_ART
    ATTR_VALUES = compteur,BMT,CAN,CCM,CM,CN,CO,EO,MR,MT,TC3
    compteur -> FeatureMerger [input 1]
    CO -> FeatureMerger [input 1]
SIGE_DISTRIBUTION.WA_EINBAUTEIL_GEO (reader ORACLE8I_DB_2)
    attributes: ACCURACY_LEVEL number(20,8), AREA number(20,8), AVG_DEV_XY number(20,8), AVG_DEV_Z number(20,8), AZIMUTH number(20,8), CALC_CODE number(4,0), CALC_NUMBER number(10,0), CLIPPING number(1,0), CREATION_CODE_XY_1 number(4,0), CREATION_CODE_XY_2 number(4,0), CREATION_CODE_XY_3 number(4,0), CREATION_CODE_XY_4 number(4,0), CREATION_CODE_XY_5 number(4,0), CREATION_CODE_Z number(4,0), DA number(10,0), DATE_CREATED date, DATE_DELETED date, DATE_MODIFIED date, DELETED number(1,0), DIM_X number(20,8), DIM_Y number(20,8), DTEXT number(1,0), ESEQ number(10,0), ETYPE number(4,0), FID number(10,0), FIELD_CODE number(4,0), FRAME number(1,0), GEO_CONSTRAINT number(1,0), GID number(10,0), ID number(10,0),
      INVISIBLE number(1,0), LABEL_FROM number(10,0), LABEL_TEXT varchar2(2000), LABEL_TO number(10,0), LINEATTRIBUTE_ID number(10,0), MUTATION_ID_CREATED number(10,0), MUTATION_ID_DELETED number(10,0), MUTATION_ID_MODIFIED number(10,0), MUTATION_STATUS_CREATED number(10,0), MUTATION_STATUS_DELETED number(10,0), M_DIRECTION number(20,8), M_DISTANCE number(20,8), ORIENTATION number(20,8), ORIGIN number(4,0), PERIMETER number(20,8), QUALITY number(10,0), SEQ number(10,0), SEQ_ETYPE number(4,0), SEQ_PARAM1 number(20,8), SEQ_PARAM1_2 number(20,8), SEQ_PARAM1_3 number(20,8), SEQ_PARAM1_4 number(20,8), SEQ_PARAM1_5 number(20,8), SEQ_PARAM2 number(20,8), SEQ_PARAM2_2 number(20,8), SEQ_PARAM2_3 number(20,8), SEQ_PARAM2_4 number(20,8), SEQ_PARAM2_5 number(20,8), SEQ_PARAM3 number(20,8), SEQ_PARAM3_2 number(20,8),
      SEQ_PARAM3_3 number(20,8), SEQ_PARAM3_4 number(20,8), SEQ_PARAM3_5 number(20,8), SOURCE number(10,0), SPATIAL_INDEX_100 number(12,0), SPATIAL_INDEX_200 number(12,0), SPATIAL_INDEX_25 number(12,0), SPATIAL_INDEX_400 number(12,0), SPATIAL_INDEX_50 number(12,0), TB_POINT_NUMBER number(15,0), TD_DA number(10,0), TD_GROUP number(10,0), TD_LAYER number(10,0), TD_NUMBER varchar2(50), TD_POINT_NUMBER number(10,0), USER_CREATED varchar2(255), USER_DELETED varchar2(255), USER_MODIFIED varchar2(255), X1 number(20,8), X2 number(20,8), X3 number(20,8), X4 number(20,8), X5 number(20,8), Y1 number(20,8), Y2 number(20,8), Y3 number(20,8), Y4 number(20,8), Y5 number(20,8), Z1 number(20,8), Z2 number(20,8),
      Z3 number(20,8), Z4 number(20,8), Z5 number(20,8), Z_DIFF number(20,8), Z_TERRAIN number(20,8)
    -> StringFormatter
StringFormatter
    FORMAT = .10f
    SRC_ATTRS = X1,Y1
    -> StringConcatenator
StringConcatenator
    PARM_LINE = POINT(,&Y1, ,&X1, )
    VAL_ATTR = WKT
    -> GeometryReplacer
GeometryReplacer
    KIND_LONG = OGC Well Known Text
    ATTR = WKT
    -> GeometryOGCValidator
GeometryOGCValidator
    VALIDATION_TYPE = Simple
    PASSED -> CoordinateSystemSetter
CoordinateSystemSetter
    COORDSYS = EPSG:21781
    -> GeometryExtractor
GeometryExtractor
    KIND_LONG = OGC Well Known Binary
    ATTR = geometry
    OGCVERSION = 1.1
    -> FeatureMerger [input 2]
FeatureMerger
    REFEEATTR = GID
    MERGE_TYPE = Geometry - Build Aggregates
    PROCESS_DUPS = No
    BUILD_INCOMPLETE = No
    REFERATTR = GID
    COMPLETE -> distribution.od_meter_subscriber (writer POSTGIS_1)
distribution.od_meter_subscriber (writer POSTGIS_1)
