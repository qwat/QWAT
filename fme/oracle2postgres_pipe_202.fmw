FME workspace oracle2postgres_pipe_202.fmw

Parameters:
- SourceDataset_ORACLE8I_DB = orcl   # Source Oracle Non-spatial Service
- SourceDataset_ORACLE8I_DB_3 = orcl   # Source Oracle Non-spatial Service
- DestDataset_POSTGIS = sige   # Destination PostGIS Dataset
- SourceDataset_POSTGRES = sige   # Source PostgreSQL Dataset
- SourceDataset_POSTGRES_5 = sige   # Source PostgreSQL Dataset

Readers:
- ORACLE8I_DB_1: ORACLE8I_DB from $(SourceDataset_ORACLE8I_DB)
- ORACLE8I_DB_2: ORACLE8I_DB from $(SourceDataset_ORACLE8I_DB_3)
- POSTGRES_1: POSTGRES from $(SourceDataset_POSTGRES)
- POSTGRES_2: POSTGRES from $(SourceDataset_POSTGRES_5)

Writers:
- POSTGIS_1: POSTGIS to $(DestDataset_POSTGIS)

Note: SIGE_DISTRIBUTION.WA_STRANG
SIGE_DISTRIBUTION.WA_STRANG (reader ORACLE8I_DB_2)
    attributes: AREA_NOMINAL number(20,8), AUFMASSSKIZZE number(1,0), A_DESAFFECTER_PDDE number(1,0), BAUJAHR number(20,0), BAUTEILTYP_ID number(20,0), BEMERKUNG varchar2(255), BESCHICHTUNG_AUSSEN varchar2(5), BESCHICHTUNG_INNEN varchar2(5), BETTUNG varchar2(5), BEZEICHNUNG1 varchar2(40), BEZEICHNUNG2 varchar2(40), BEZEICHNUNG3 varchar2(40), BEZEICHNUNG4 varchar2(40), BEZEICHNUNG5 varchar2(40), BEZEICHNUNG6 varchar2(40), CALCUL_HYDRAULIQUE number(1,0), COMMUNE varchar2(50), DELETED number(1,0), DIAM_INT_PDDE number(20,5), DOSSIER varchar2(10), DRUCKZONE_ID number(20,0), DURCHMESSER_AUSSEN number(20,5), DURCHMESSER_INNEN number(20,5), EIGENTUMSVERHAELTNIS varchar2(5), F1 varchar2(20), F2 varchar2(20), F3 varchar2(20), F4 varchar2(20), FABRIKATIONSDATUM date, FID number(10,0),
      FID_LAGEBEZEICHNUNG number(10,0), FLST_KENNZEICHEN_OF varchar2(25), FLST_NENNER number(20,0), FLST_NR number(20,0), FLST_ZAEHLER number(20,0), FOLIO varchar2(15), FUNKTION varchar2(5), GEFAELLE number(20,5), GEMARKUNG number(20,0), GID number(10,0), HERSTELLER_ID number(20,0), ID_VERLEGESTATUS number(10,0), ISOLATION varchar2(30), KORROSSIONSSCHUTZ number(20,0), LAENGE_NICHTOEFFENTLICH number(10,5), LAENGE_OEFFENTLICH number(10,5), LAGE varchar2(5), LAGEGENAUIGKEIT varchar2(5), LEITUNGSANFANG varchar2(25), LEITUNGSENDE varchar2(25), MATERIAL varchar2(10), MATERIALQUALITAET varchar2(15), NAME varchar2(61), NAME2 varchar2(50), NENNDRUCK number(20,5), NENNWEITE varchar2(15), NK_ID number(20,0), ORTSTEIL varchar2(20), POOL number(20,0), ROHRRAUHEIT number(20,5),
      SCHUBSICHERUNG_ID number(20,0), STANDORT varchar2(50), STATUS varchar2(5), STRANGLAENGE number(20,5), STRANGLAENGE_BERECHNET number(20,5), TUYAU_PROTECTEUR number(10,0), VERBINDUNGSART varchar2(15), VERLEGEART varchar2(5), VERLEGEDATUM date, VERLEGEFIRMA_ID number(10,0), VERSORGUNGSGEBIET_ID number(20,0), VK_ID number(20,0), V_COMMUNE number(10,0), WANDSTAERKE number(20,5), WASSERQUALITAET varchar2(5)
    -> AttributeFilter
Note: Retirer les DELETED
AttributeFilter
    ATTR_NAME = DELETED
    ATTR_VALUES = 0
    0 -> StringConcatenator
Note: Concaténer Bemerkung / et Bezeichnung1 / (remarks)
StringConcatenator
    PARM_LINE = &BEMERKUNG,  / ,&BEZEICHNUNG1
    VAL_ATTR = remarks
    -> AttributeFilter_3
Note: search empty remarks
AttributeFilter_3
    ATTR_NAME = remarks
    ATTR_VALUES = " / ,  / "
    <UNFILTERED> -> AttributeRemover
    <BLANK> -> AttributeRemover
    / -> AttributeSetter_2
Note: delete remarks
AttributeSetter_2
    DEST_ATTR = &remarks
    -> AttributeRemover
Note: Supprimer les champs inutile
AttributeRemover
    REMOVE_ATTRS = AREA_NOMINAL,AUFMASSSKIZZE,A_DESAFFECTER_PDDE,BAUTEILTYP_ID,BEMERKUNG,BETTUNG,BEZEICHNUNG1,BEZEICHNUNG2,BEZEICHNUNG3,BEZEICHNUNG4,BEZEICHNUNG5,BEZEICHNUNG6,CALCUL_HYDRAULIQUE,COMMUNE,DIAM_INT_PDDE,F1,F2,F3,F4,FABRIKATIONSDATUM,FID_LAGEBEZEICHNUNG,FLST_KENNZEICHEN_OF,FLST_NENNER,FLST_NR,FLST_ZAEHLER,GEFAELLE,GEMARKUNG,HERSTELLER_ID,ID_VERLEGESTATUS,ISOLATION,KORROSSIONSSCHUTZ,LAENGE_NICHTOEFFENTLICH,LAENGE_OEFFENTLICH,LAGE,LEITUNGSANFANG,LEITUNGSENDE,MATERIALQUALITAET,NAME,NAME2,NK_ID,ORTSTEIL,POOL,ROHRRAUHEIT,SCHUBSICHERUNG_ID,STANDORT,STRANGLAENGE,VERBINDUNGSART,VERLEGEDATUM,VERLEGEFIRMA_ID,VERSORGUNGSGEBIET_ID,VK_ID,V_COMMUNE,WASSERQUALITAET
    -> pipe_function [input 1]
SIGE_DISTRIBUTION.WA_STRANG_GEO (reader ORACLE8I_DB_1)
    attributes: ACCURACY_LEVEL number(20,8), AREA number(20,8), AVG_DEV_XY number(20,8), AVG_DEV_Z number(20,8), AZIMUTH number(20,8), CALC_CODE number(4,0), CALC_NUMBER number(10,0), CLIPPING number(1,0), CREATION_CODE_XY_1 number(4,0), CREATION_CODE_XY_2 number(4,0), CREATION_CODE_XY_3 number(4,0), CREATION_CODE_XY_4 number(4,0), CREATION_CODE_XY_5 number(4,0), CREATION_CODE_Z number(4,0), DA number(10,0), DATE_CREATED date, DATE_DELETED date, DATE_MODIFIED date, DELETED number(1,0), DIM_X number(20,8), DIM_Y number(20,8), DTEXT number(1,0), ESEQ number(10,0), ETYPE number(4,0), FID number(10,0), FIELD_CODE number(4,0), FRAME number(1,0), GEO_CONSTRAINT number(1,0), GID number(10,0), ID number(10,0),
      INVISIBLE number(1,0), LABEL_FROM number(10,0), LABEL_TEXT varchar2(2000), LABEL_TO number(10,0), LINEATTRIBUTE_ID number(10,0), MUTATION_ID_CREATED number(10,0), MUTATION_ID_DELETED number(10,0), MUTATION_ID_MODIFIED number(10,0), MUTATION_STATUS_CREATED number(10,0), MUTATION_STATUS_DELETED number(10,0), M_DIRECTION number(20,8), M_DISTANCE number(20,8), ORIENTATION number(20,8), ORIGIN number(4,0), PERIMETER number(20,8), QUALITY number(10,0), SEQ number(10,0), SEQ_ETYPE number(4,0), SEQ_PARAM1 number(20,8), SEQ_PARAM1_2 number(20,8), SEQ_PARAM1_3 number(20,8), SEQ_PARAM1_4 number(20,8), SEQ_PARAM1_5 number(20,8), SEQ_PARAM2 number(20,8), SEQ_PARAM2_2 number(20,8), SEQ_PARAM2_3 number(20,8), SEQ_PARAM2_4 number(20,8), SEQ_PARAM2_5 number(20,8), SEQ_PARAM3 number(20,8), SEQ_PARAM3_2 number(20,8),
      SEQ_PARAM3_3 number(20,8), SEQ_PARAM3_4 number(20,8), SEQ_PARAM3_5 number(20,8), SOURCE number(10,0), SPATIAL_INDEX_100 number(12,0), SPATIAL_INDEX_200 number(12,0), SPATIAL_INDEX_25 number(12,0), SPATIAL_INDEX_400 number(12,0), SPATIAL_INDEX_50 number(12,0), TB_POINT_NUMBER number(15,0), TD_DA number(10,0), TD_GROUP number(10,0), TD_LAYER number(10,0), TD_NUMBER varchar2(50), TD_POINT_NUMBER number(10,0), USER_CREATED varchar2(255), USER_DELETED varchar2(255), USER_MODIFIED varchar2(255), X1 number(20,8), X2 number(20,8), X3 number(20,8), X4 number(20,8), X5 number(20,8), Y1 number(20,8), Y2 number(20,8), Y3 number(20,8), Y4 number(20,8), Y5 number(20,8), Z1 number(20,8), Z2 number(20,8),
      Z3 number(20,8), Z4 number(20,8), Z5 number(20,8), Z_DIFF number(20,8), Z_TERRAIN number(20,8)
    -> liner
liner
    AttributeRemover_4_OUTPUT_86 -> FeatureMerger [input 2]
Note: distribution.pipe_material
distribution.pipe_material (reader POSTGRES_2)
    attributes: id serial,PRIKEY, short_name varchar(6), name varchar(30), diameter varchar(10), diameter_internal varchar(10), diameter_external varchar(10), _fancy_name varchar(16)
    -> pipe_material [input 2]
Note: distribution.pipe_function
distribution.pipe_function (reader POSTGRES_1)
    attributes: id serial,PRIKEY, function varchar(80),PRIKEY, schema_view bool
    -> pipe_function [input 2]
pipe_function
    joined -> ValueMapper_id_status
Note: pipe_status
ValueMapper_id_status: AttributeValueMapper
    LUT = E,1,EA,6,F,7,A,4,D,3,,0
    SRC = STATUS
    VAL_ATTR = id_status
    DIRECTION = Forward
    -> AttributeValueMapper_3
Note: protection
AttributeValueMapper_3
    LUT = 10,1,2,2,3,3,4,4,6,5,5,6,7,7,8,8,9,9,11,10,12,11,,
    SRC = TUYAU_PROTECTEUR
    VAL_ATTR = id_protection
    DIRECTION = Forward
    -> pipe_material [input 1]
pipe_material
    ok -> AttributeRenamer
Note: Renomer les champs
AttributeRenamer
    ATTR_LIST = coating_internal_material_id,BESCHICHTUNG_AUSSEN,coating_external_material_id,BESCHICHTUNG_INNEN,material_ext_diam,DURCHMESSER_AUSSEN,material_int_diam,DURCHMESSER_INNEN,id_distributor,EIGENTUMSVERHAELTNIS,pressure_nominale,NENNDRUCK,material_nominal_diam,NENNWEITE,length3d,STRANGLAENGE_BERECHNET,material_thickness,WANDSTAERKE,year,BAUJAHR,id,FID,folder,DOSSIER,z_folio,FOLIO,status,STATUS,z_deleted,DELETED
    -> AttributeValueMapper
Note: id_precision
AttributeValueMapper
    LUT = IP,1,P,2,L,3,D,4,I,5,,5
    SRC = LAGEGENAUIGKEIT
    VAL_ATTR = id_precision
    DIRECTION = Forward
    -> distributor_SIGE
distributor_SIGE: NullAttributeReplacer
    NEW_VALUE = 1
    SRC_ATTRS = id_distributor
    -> AttributeValueMapper_2
Note: id_install_method
AttributeValueMapper_2
    LUT = F,1,CH,2,AL,3,SP,4,PRO,5,B,6,G,7,I,8,,8
    SRC = VERLEGEART
    VAL_ATTR = id_install_method
    DIRECTION = Forward
    -> AttributeFilter_2
Note: Selectionne les dates nulles ou 0
AttributeFilter_2
    ATTR_NAME = year
    ATTR_VALUES = 0
    0 -> AttributeSetter
    <BLANK> -> AttributeSetter
    <UNFILTERED> -> NullAttributeReplacer
Note: Changer les dates a 1899
AttributeSetter
    VAL = 1899
    DEST_ATTR = year
    -> AttributeCreator
Note: Remplace les dates null a 1899
NullAttributeReplacer
    NEW_VALUE = 1899
    SRC_ATTRS = year
    -> AttributeCreator
Note: Creation des attributs manquants
AttributeCreator
    ATTR_LIST = id_parent,NULL,schema_force_view,NULL
    -> FeatureMerger [input 1]
FeatureMerger
    GROUP_BY = GID
    REFEEATTR = GID
    MERGE_TYPE = Geometry - Build Aggregates
    PROCESS_DUPS = No
    BUILD_INCOMPLETE = No
    REFERATTR = GID
    COMPLETE -> distribution.pipe (writer POSTGIS_1)
distribution.pipe (writer POSTGIS_1)
    attributes: coating_external_material_id char(20), coating_internal_material_id char(20), folder char(20), id serial,PRIKEY, id_function int4, id_install_method char(20), id_material int4, id_distributor char(20), id_parent int4, id_precision char(20), id_status int4, material_ext_diam char(20), material_int_diam char(20), material_nominal_diam char(20), material_thickness char(20), pressure_nominale char(20), protection_coating_detail char(20), remarks char(20), schema_force_view bool, year char(20)

FME custom transformer CONDUITE_BLONAY

FME custom transformer pipe_material

TOPOBASE (input)
    -> AttributeFilter
Note: Unknown material => Inconnu
AttributeFilter
    ATTR_NAME = MATERIAL
    ATTR_VALUES = ""
    "" -> AttributeSetter
    <BLANK> -> AttributeSetter
    <UNFILTERED> -> Tester
Note: Detect numeric material / => Inconnu
Tester
    TEST_CLAUSE:
      TEST @Value(MATERIAL) > 1
      TEST @Value(MATERIAL) < 1100
    BOOL_OP = AND
    TEST_LIST = &MATERIAL,>,1,&MATERIAL,<,1100
    TEST_MODE = Automatic
    FAILED -> AttributeFilter_2
    PASSED -> AttributeSetter
Note: Set MATERIAL = Inconnu
AttributeSetter
    VAL = Inconnu
    DEST_ATTR = &MATERIAL
    -> AttributeFilter_2
Note: Unknown diameter=> inconnu
AttributeFilter_2
    ATTR_NAME = NENNWEITE
    ATTR_VALUES = ""
    "" -> AttributeSetter_2
    <BLANK> -> AttributeSetter_2
    <UNFILTERED> -> StringConcatenator_2
Note: Set NENNWEITE = inconnu
AttributeSetter_2
    VAL = inconnu
    DEST_ATTR = &NENNWEITE
    -> StringConcatenator_2
Note: Concat MATERIAL NENNWEITE
StringConcatenator_2
    PARM_LINE = &MATERIAL, ,&NENNWEITE
    VAL_ATTR = joined_material_text
    -> AttributeFilter_3
Note: Inonnu inconnu => Inconnu
AttributeFilter_3
    ATTR_NAME = joined_material_text
    ATTR_VALUES = Inconnu inconnu
    <UNFILTERED> -> FeatureMerger_2 [input 1]
    Inconnu inconnu -> AttributeSetter_3
Note: Set joined_material = Inconnu
AttributeSetter_3
    VAL = Inconnu
    DEST_ATTR = &joined_material_text
    -> FeatureMerger_2 [input 1]
POSTGIS_MATERIAL (input)
    -> AttributeRenamer_2
Note: renommer id to id_material
AttributeRenamer_2
    ATTR_LIST = id_material,id
    -> FeatureMerger_2 [input 2]
FeatureMerger_2
    REFEEATTR = _fancy_name
    MERGE_TYPE = Attributes Only
    PROCESS_DUPS = No
    BUILD_INCOMPLETE = No
    REFERATTR = joined_material_text
    COMPLETE -> ok (output)
    EMPTY -> material_error (output)
    INCOMPLETE -> material_error (output)
    EMPTY -> Logger_2
    INCOMPLETE -> Logger_2
ok (output)
material_error (output)
Logger_2
    MESSAGE = Feature is:
    MAXFEATS = 20
    MAXCOORDS = 20
Logger
    MESSAGE = Feature is:
    MAXFEATS = 20
    MAXCOORDS = 20

FME custom transformer pipe_function

pipe (input)
    -> FeatureMerger [input 1]
function (input)
    -> AttributeValueMapper
Note: Create short name from TB
AttributeValueMapper
    LUT = "conduite de refoulement",REF,"Conduite de transport",A,"Conduite de purge",CPU,"Conduite d'hydrant",CH,"Conduite de vidange",CV,Inconnu,I,"Conduite de distribution",CD,"Branchement commun",CB,By-pass,BP,"Branchement privé",CA,"Conduite haute pression",HP,"Drain captant",DC,,0
    SRC = function
    VAL_ATTR = _TBFunktion
    DIRECTION = Forward
    -> AttributeRenamer
Note: Rename id to id_function
AttributeRenamer
    ATTR_LIST = id_function,id
    -> FeatureMerger [input 2]
FeatureMerger
    REFEEATTR = _TBFunktion
    MERGE_TYPE = Attributes Only
    PROCESS_DUPS = No
    BUILD_INCOMPLETE = No
    REFERATTR = FUNKTION
    COMPLETE -> AttributeRemover
    INCOMPLETE -> incomplete_2 (output)
    EMPTY -> incomplete_2 (output)
    DUPLICATE_SUPPLIER -> incomplete_2 (output)
    UNREFERENCED -> unused_material_2 (output)
AttributeRemover
    REMOVE_ATTRS = FUNKTION,_TBFunktion,schema_view
    -> joined (output)
joined (output)
incomplete_2 (output)
unused_material_2 (output)
unused_material (output)

FME custom transformer pipe_druckzone

FME custom transformer liner

AttributeRemover_2_INPUT_39 (input)
    -> AttributeRemover_2
Note: Champs inutiles
AttributeRemover_2
    REMOVE_ATTRS = ACCURACY_LEVEL,AREA,AVG_DEV_XY,AVG_DEV_Z,AZIMUTH,CALC_CODE,CALC_NUMBER,CLIPPING,CREATION_CODE_XY_1,CREATION_CODE_XY_2,CREATION_CODE_XY_3,CREATION_CODE_XY_4,CREATION_CODE_XY_5,CREATION_CODE_Z,DA,DATE_CREATED,DATE_DELETED,DATE_MODIFIED,DELETED,DIM_X,DIM_Y,DTEXT,ESEQ,ETYPE,FID,FIELD_CODE,FRAME,GEO_CONSTRAINT,ID,INVISIBLE,LABEL_FROM,LABEL_TEXT,LABEL_TO,LINEATTRIBUTE_ID,MUTATION_ID_CREATED,MUTATION_ID_DELETED,MUTATION_ID_MODIFIED,MUTATION_STATUS_CREATED,MUTATION_STATUS_DELETED,M_DIRECTION,M_DISTANCE,ORIENTATION,ORIGIN,PERIMETER,QUALITY,SEQ_ETYPE,SEQ_PARAM1,SEQ_PARAM1_2,SEQ_PARAM1_3,SEQ_PARAM1_4,SEQ_PARAM1_5,SEQ_PARAM2,SEQ_PARAM2_2,SEQ_PARAM2_3,SEQ_PARAM2_4,SEQ_PARAM2_5,SEQ_PARAM3,SEQ_PARAM3_2,SEQ_PARAM3_3,SEQ_PARAM3_4,SEQ_PARAM3_5,SOURCE,SPATIAL_INDEX_100,SPATIAL_INDEX_200,SPATIAL_INDEX_25,SPATIAL_INDEX_400,SPATIAL_INDEX_50,TB_POINT_NUMBER,TD_DA,TD_GROUP,TD_LAYER,TD_NUMBER,TD_POINT_NUMBER,USER_CREATED,USER_DELETED,USER_MODIFIED,X2,X3,X4,X5,Y2,Y3,Y4,Y5,Z1,Z2,Z3,Z4,Z5,Z_DIFF,Z_TERRAIN
    -> Sorter
Note: Tri par GID puis par SEQ
Sorter
    SORT_PARM = GID NUMERIC ASCENDING SEQ NUMERIC ASCENDING
    SORTED -> StringFormatter
Note: Transforme les coordonnées en texte
StringFormatter
    FORMAT = .10f
    SRC_ATTRS = X1,Y1
    -> StringConcatenator_2
Note: Concatene X et Y dans xy
StringConcatenator_2
    PARM_LINE = &Y1, ,&X1
    VAL_ATTR = xy
    -> AttributeRemover_3
Note: Suppression X et Y
AttributeRemover_3
    REMOVE_ATTRS = X1,Y1
    -> ListBuilder
Note: Grouper les éléments par GID (triés en SEQ)
ListBuilder
    LIST_NAME = list
    GRP_BY = GID
    -> ListConcatenator
Note: Concatene les xy des memes conduites
ListConcatenator
    SEP = ", "
    VAL_ATTR = _linestring
    LIST_ATTR = list{}.xy
    -> AttributeCreator_2
Note: Ajout des champs gauche et droite du WKT
AttributeCreator_2
    ATTR_LIST = left,LINESTRING(,right,)
    -> StringConcatenator_3
Note: Concatene avec les parenthèses
StringConcatenator_3
    PARM_LINE = &left,&_linestring,&right
    VAL_ATTR = linestring
    -> AttributeRemover_4
Note: Suppression des champs intermediaires
AttributeRemover_4
    REMOVE_ATTRS = _linestring,left,right
    -> GeometryReplacer
Note: Create GEOM from WKT
GeometryReplacer
    KIND_LONG = OGC Well Known Text
    ATTR = linestring
    -> GeometryOGCValidator
GeometryOGCValidator
    VALIDATION_TYPE = Valid
    PASSED -> CoordinateSystemSetter
CoordinateSystemSetter
    COORDSYS = EPSG:21781
    -> GeometryExtractor
Note: Write WKB from GEOM
GeometryExtractor
    KIND_LONG = OGC Well Known Binary
    ATTR = geometry
    OGCVERSION = 1.1
    -> AttributeRemover_4_OUTPUT_86 (output)
AttributeRemover_4_OUTPUT_86 (output)

FME custom transformer CONDUITE_SIGE
