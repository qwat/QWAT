FME workspace oracle2postgres_printmaps_75.fmw

Parameters:
- SourceDataset_ORACLE8I = orcl   # Source Oracle Spatial Object Service
- SourceDataset_ORACLE8I_DB = orcl   # Source Oracle Non-spatial Service
- DestDataset_POSTGIS = sige   # Destination PostGIS Dataset

Readers:
- ORACLE8I_1: ORACLE8I from $(SourceDataset_ORACLE8I) in EPSG:21781
- ORACLE8I_DB_1: ORACLE8I_DB from $(SourceDataset_ORACLE8I_DB) in EPSG:21781

Writers:
- POSTGIS_1: POSTGIS to $(DestDataset_POSTGIS)

Note: SIGE_FOLIO
SIGE_DISTRIBUTION.SIGE_FOLIO (reader ORACLE8I_1)
    attributes: AREA_GERECHNET number(20,8), AREA_NOMINAL number(20,8), COM varchar2(10), COMMUNE number(10,0), DELETED number(1,0), FID number(10,0), GID number(10,0), MENSU_NUM number(1,0), NO_FOLIO varchar2(10)
    -> AttributeFilter
Note: Retirer deleted
AttributeFilter
    ATTR_NAME = DELETED
    ATTR_VALUES = 0
    0 -> AttributeRenamer
Note: Renommage
AttributeRenamer
    ATTR_LIST = short_name,NO_FOLIO
    -> FeatureMerger [input 1]
Note: SIGE_FOLIO_GEO
SIGE_DISTRIBUTION.SIGE_FOLIO_GEO (reader ORACLE8I_DB_1)
    attributes: ACCURACY_LEVEL number(20,8), AREA number(20,8), AVG_DEV_XY number(20,8), AVG_DEV_Z number(20,8), AZIMUTH number(20,8), CALC_CODE number(4,0), CALC_NUMBER number(10,0), CLIPPING number(1,0), CREATION_CODE_XY_1 number(4,0), CREATION_CODE_XY_2 number(4,0), CREATION_CODE_XY_3 number(4,0), CREATION_CODE_XY_4 number(4,0), CREATION_CODE_XY_5 number(4,0), CREATION_CODE_Z number(4,0), DA number(10,0), DATE_CREATED date, DATE_DELETED date, DATE_MODIFIED date, DELETED number(1,0), DIM_X number(20,8), DIM_Y number(20,8), DTEXT number(1,0), ESEQ number(10,0), ETYPE number(4,0), FID number(10,0), FIELD_CODE number(4,0), FRAME number(1,0), GEO_CONSTRAINT number(1,0), GID number(10,0), ID number(10,0),
      INVISIBLE number(1,0), LABEL_FROM number(10,0), LABEL_TEXT varchar2(2000), LABEL_TO number(10,0), LINEATTRIBUTE_ID number(10,0), MUTATION_ID_CREATED number(10,0), MUTATION_ID_DELETED number(10,0), MUTATION_ID_MODIFIED number(10,0), MUTATION_STATUS_CREATED number(10,0), MUTATION_STATUS_DELETED number(10,0), M_DIRECTION number(20,8), M_DISTANCE number(20,8), ORIENTATION number(20,8), ORIGIN number(4,0), PERIMETER number(20,8), QUALITY number(10,0), SEQ number(10,0), SEQ_ETYPE number(4,0), SEQ_PARAM1 number(20,8), SEQ_PARAM1_2 number(20,8), SEQ_PARAM1_3 number(20,8), SEQ_PARAM1_4 number(20,8), SEQ_PARAM1_5 number(20,8), SEQ_PARAM2 number(20,8), SEQ_PARAM2_2 number(20,8), SEQ_PARAM2_3 number(20,8), SEQ_PARAM2_4 number(20,8), SEQ_PARAM2_5 number(20,8), SEQ_PARAM3 number(20,8), SEQ_PARAM3_2 number(20,8),
      SEQ_PARAM3_3 number(20,8), SEQ_PARAM3_4 number(20,8), SEQ_PARAM3_5 number(20,8), SOURCE number(10,0), SPATIAL_INDEX_100 number(12,0), SPATIAL_INDEX_200 number(12,0), SPATIAL_INDEX_25 number(12,0), SPATIAL_INDEX_400 number(12,0), SPATIAL_INDEX_50 number(12,0), TB_POINT_NUMBER number(15,0), TD_DA number(10,0), TD_GROUP number(10,0), TD_LAYER number(10,0), TD_NUMBER varchar2(50), TD_POINT_NUMBER number(10,0), USER_CREATED varchar2(255), USER_DELETED varchar2(255), USER_MODIFIED varchar2(255), X1 number(20,8), X2 number(20,8), X3 number(20,8), X4 number(20,8), X5 number(20,8), Y1 number(20,8), Y2 number(20,8), Y3 number(20,8), Y4 number(20,8), Y5 number(20,8), Z1 number(20,8), Z2 number(20,8),
      Z3 number(20,8), Z4 number(20,8), Z5 number(20,8), Z_DIFF number(20,8), Z_TERRAIN number(20,8)
    -> liner
liner
    AttributeRemover_4_OUTPUT_86 -> FeatureMerger [input 2]
FeatureMerger
    GROUP_BY = GID
    REFEEATTR = GID
    MERGE_TYPE = Geometry - Build Aggregates
    PROCESS_DUPS = No
    BUILD_INCOMPLETE = No
    REFERATTR = GID
    COMPLETE -> distribution.printmaps (writer POSTGIS_1)
distribution.printmaps (writer POSTGIS_1)
Visualizer

FME custom transformer CONDUITE_BLONAY

FME custom transformer polygoner

AttributeRemover_2_INPUT_0 (input)
    -> AttributeRemover_2
Note: Champs inutiles
AttributeRemover_2
    REMOVE_ATTRS = ACCURACY_LEVEL,AREA,AVG_DEV_XY,AVG_DEV_Z,AZIMUTH,CALC_CODE,CALC_NUMBER,CLIPPING,CREATION_CODE_XY_1,CREATION_CODE_XY_2,CREATION_CODE_XY_3,CREATION_CODE_XY_4,CREATION_CODE_XY_5,CREATION_CODE_Z,DA,DATE_CREATED,DATE_DELETED,DATE_MODIFIED,DELETED,DIM_X,DIM_Y,DTEXT,ESEQ,ETYPE,FID,FIELD_CODE,FRAME,GEO_CONSTRAINT,ID,INVISIBLE,LABEL_FROM,LABEL_TEXT,LABEL_TO,LINEATTRIBUTE_ID,MUTATION_ID_CREATED,MUTATION_ID_DELETED,MUTATION_ID_MODIFIED,MUTATION_STATUS_CREATED,MUTATION_STATUS_DELETED,M_DIRECTION,M_DISTANCE,ORIENTATION,ORIGIN,PERIMETER,QUALITY,SEQ_ETYPE,SEQ_PARAM1,SEQ_PARAM1_2,SEQ_PARAM1_3,SEQ_PARAM1_4,SEQ_PARAM1_5,SEQ_PARAM2,SEQ_PARAM2_2,SEQ_PARAM2_3,SEQ_PARAM2_4,SEQ_PARAM2_5,SEQ_PARAM3,SEQ_PARAM3_2,SEQ_PARAM3_3,SEQ_PARAM3_4,SEQ_PARAM3_5,SOURCE,SPATIAL_INDEX_100,SPATIAL_INDEX_200,SPATIAL_INDEX_25,SPATIAL_INDEX_400,SPATIAL_INDEX_50,TB_POINT_NUMBER,TD_DA,TD_GROUP,TD_LAYER,TD_NUMBER,TD_POINT_NUMBER,USER_CREATED,USER_DELETED,USER_MODIFIED,X2,X3,X4,X5,Y2,Y3,Y4,Y5,Z1,Z2,Z3,Z4,Z5,Z_DIFF,Z_TERRAIN
    -> Sorter
Note: Tri par GID puis par SEQ
Sorter
    SORT_PARM = GID NUMERIC ASCENDING SEQ NUMERIC ASCENDING
    SORTED -> StringFormatter
Note: Transforme les coordonnées en texte
StringFormatter
    FORMAT = .10f
    SRC_ATTRS = X1,Y1
    -> StringConcatenator_2
Note: Concatene X et Y dans xy
StringConcatenator_2
    PARM_LINE = &Y1, ,&X1
    VAL_ATTR = xy
    -> AttributeRemover_3
Note: Suppression X et Y
AttributeRemover_3
    REMOVE_ATTRS = X1,Y1
    -> ListBuilder
Note: Grouper les éléments par GID (triés en SEQ)
ListBuilder
    LIST_NAME = list
    GRP_BY = GID
    -> ListConcatenator
Note: Concatene les xy des memes conduites
ListConcatenator
    SEP = ", "
    VAL_ATTR = _linestring
    LIST_ATTR = list{}.xy
    -> AttributeCreator_2
Note: Ajout des champs gauche et droite du WKT
AttributeCreator_2
    ATTR_LIST = left,POLYGON((,right,))
    -> StringConcatenator_3
Note: Concatene avec les parenthèses
StringConcatenator_3
    PARM_LINE = &left,&_linestring,&right
    VAL_ATTR = linestring
    -> AttributeRemover_4
Note: Suppression des champs intermediaires
AttributeRemover_4
    REMOVE_ATTRS = _linestring,left,right
    -> GeometryReplacer
Note: Create GEOM from WKT
GeometryReplacer
    KIND_LONG = OGC Well Known Text
    ATTR = linestring
    -> GeometryOGCValidator
GeometryOGCValidator
    VALIDATION_TYPE = Valid
    PASSED -> CoordinateSystemSetter
CoordinateSystemSetter
    COORDSYS = EPSG:21781
    -> GeometryExtractor
Note: Write WKB from GEOM
GeometryExtractor
    KIND_LONG = OGC Well Known Binary
    ATTR = geometry
    OGCVERSION = 1.1
    -> GeometryExtractor_OUTPUT_35 (output)
GeometryExtractor_OUTPUT_35 (output)

FME custom transformer liner

AttributeRemover_2_INPUT_39 (input)
    -> polygoner
polygoner
    GeometryExtractor_OUTPUT_35 -> AttributeRemover_4_OUTPUT_86 (output)
AttributeRemover_4_OUTPUT_86 (output)

FME custom transformer CONDUITE_SIGE
