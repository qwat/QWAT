FME workspace oracle2postgres_4_installation_202.fmw

Parameters:
- DestDataset_POSTGIS = sige   # Destination PostGIS Dataset
- SourceDataset_ORACLE8I_DB_3 = orcl   # Source Oracle Non-spatial Service
- SourceDataset_POSTGRES = sige   # Source PostgreSQL Dataset
- SourceDataset_ORACLE8I_DB = orcl   # Source Oracle Non-spatial Service
- SourceDataset_POSTGRES_3 = sige   # Source PostgreSQL Dataset

Readers:
- ORACLE8I_DB_1: ORACLE8I_DB from $(SourceDataset_ORACLE8I_DB_3) in EPSG:21781
- POSTGRES_1: POSTGRES from $(SourceDataset_POSTGRES) in EPSG:21781
- ORACLE8I_DB_2: ORACLE8I_DB from $(SourceDataset_ORACLE8I_DB)
- POSTGRES_2: POSTGRES from $(SourceDataset_POSTGRES_3) in EPSG:21781

Writers:
- POSTGIS_1: POSTGIS to $(DestDataset_POSTGIS) in EPSG:21781

Note: WA_BAUWERK
SIGE_DISTRIBUTION_SCHEMA.WA_BAUWERK (reader ORACLE8I_DB_1)
    attributes: ABMESSUNG varchar2(25), ARCHIVNUMMER varchar2(50), AREA_NOMINAL number(20,8), AUTRE_EQUIPEMENT varchar2(50), BAUJAHR number(20,0), BAUWERK_TYP varchar2(15), BEMERKUNG varchar2(250), CHAUFFAGE varchar2(30), DATENUEBERTRAGUNG number(1,0), DELETED number(1,0), DESHUMIDIFICATEUR varchar2(30), DRUCKZONE_ID number(10,0), EIGENTUMSVERHAELTNIS varchar2(5), EINBAUORT varchar2(50), EINBAU_DATUM date, ELEC number(1,0), F1 varchar2(50), F2 varchar2(50), F3 varchar2(50), FID number(10,0), FID_BAUWERK number(10,0), FID_EIGENTUEMER number(10,0), FID_GEMEINDE number(10,0), FID_LAGEBEZEICHNUNG number(10,0), FILTRE_AIR varchar2(30), FLST_KENNZEICHEN_OF varchar2(25), FLST_NENNER number(20,0), FLST_NR number(20,0), FLST_ZAEHLER number(20,0), GEMARKUNG number(20,0),
      GID number(10,0), HAUSNUMMER number(10,0), HAUSNUMMER_ERG varchar2(10), HOEHE_GEBAEUDEBOLZEN number(20,5), ID_DISTRIBUTEUR_2 varchar2(5), ID_FONCTION_2 number(10,0), ID_FUNKTION number(10,0), ID_HERSTELLER number(10,0), ID_ZONE_PRESSION_2 number(10,0), INVENTAIRE date, LAGEGENAUIGKEIT varchar2(5), NAME varchar2(100), NAME2 varchar2(100), PLAN_EAU number(1,0), POINT_NUMBER varchar2(50), POOL number(1,0), PRIVE number(1,0), SCHEMA number(1,0), SCHEMA_ELEC number(1,0), STANDORT varchar2(100), STATUS varchar2(5), STROM_STATION varchar2(50), TAB_ELEC_1 varchar2(20), TAB_ELEC_2 varchar2(20), TB_POINT_NUMBER number(15,0), TELEGESTION_1 varchar2(20), TELEGESTION_2 varchar2(20), TELEGESTION_3 varchar2(20), ZUTRITTSUEBERWACHUNG number(20,0)
    -> AttributeFilter
AttributeFilter
    ATTR_NAME = DELETED
    ATTR_VALUES = 0
    0 -> AttributeRenamer
AttributeRenamer
    ATTR_LIST = id,FID,name,NAME,distributor,EIGENTUMSVERHAELTNIS,remarks,BEMERKUNG,year,BAUJAHR,parcel,FLST_NR,eca,HAUSNUMMER,identification,ARCHIVNUMMER
    -> status
status: AttributeValueMapper
    LUT = E,1,H,2,A,4,D,3,NONC,3,PR,6,,0
    SRC = STATUS
    VAL_ATTR = id_status
    DIRECTION = Forward
    -> NullAttributeReplacer
Note: defautl distributor = SIGE
NullAttributeReplacer
    NEW_VALUE = 1
    SRC_ATTRS = distributor
    -> AttributeValueMapper_2
Note: distributor
AttributeValueMapper_2
    LUT = 1,1,2,2,3,3,4,4,5,6,6,8,7,9,8,10,9,7,10,11,11,12,12,13,13,14,;,1,,0
    SRC = distributor
    VAL_ATTR = id_distributor
    DIRECTION = Forward
    -> year
year
    AttributeCreator_OUTPUT_9 -> open_water_schema
open_water_schema: AttributeValueMapper
    LUT = 1,1,,0
    SRC = PLAN_EAU
    VAL_ATTR = open_water_schema
    DIRECTION = Forward
    -> installation_type [input 2]
SIGE_DISTRIBUTION_SCHEMA.EP_OUVRAGE_POS_EXACTE (reader ORACLE8I_DB_2)
    attributes: DELETED number(1,0), FID number(10,0), GID number(10,0), OUVRAGE number(10,0), TB_POINT_NUMBER number(15,0)
    -> FeatureMerger_3 [input 1]
Note: OUVRAGE_POS_EXACTE_GEO
SIGE_DISTRIBUTION_SCHEMA.EP_OUVRAGE_POS_EXACTE_GEO (reader ORACLE8I_DB_2)
    attributes: ACCURACY_LEVEL number(20,8), AREA number(20,8), AVG_DEV_XY number(20,8), AVG_DEV_Z number(20,8), AZIMUTH number(20,8), CALC_CODE number(4,0), CALC_NUMBER number(10,0), CLIPPING number(1,0), CREATION_CODE_XY_1 number(4,0), CREATION_CODE_XY_2 number(4,0), CREATION_CODE_XY_3 number(4,0), CREATION_CODE_XY_4 number(4,0), CREATION_CODE_XY_5 number(4,0), CREATION_CODE_Z number(4,0), DA number(10,0), DATE_CREATED date, DATE_DELETED date, DATE_MODIFIED date, DELETED number(1,0), DIM_X number(20,8), DIM_Y number(20,8), DTEXT number(1,0), ESEQ number(10,0), ETYPE number(4,0), FID number(10,0), FIELD_CODE number(4,0), FRAME number(1,0), GEO_CONSTRAINT number(1,0), GID number(10,0), ID number(10,0),
      INVISIBLE number(1,0), LABEL_FROM number(10,0), LABEL_TEXT varchar2(2000), LABEL_TO number(10,0), LINEATTRIBUTE_ID number(10,0), MUTATION_ID_CREATED number(10,0), MUTATION_ID_DELETED number(10,0), MUTATION_ID_MODIFIED number(10,0), MUTATION_STATUS_CREATED number(10,0), MUTATION_STATUS_DELETED number(10,0), M_DIRECTION number(20,8), M_DISTANCE number(20,8), ORIENTATION number(20,8), ORIGIN number(4,0), PERIMETER number(20,8), QUALITY number(10,0), SEQ number(10,0), SEQ_ETYPE number(4,0), SEQ_PARAM1 number(20,8), SEQ_PARAM1_2 number(20,8), SEQ_PARAM1_3 number(20,8), SEQ_PARAM1_4 number(20,8), SEQ_PARAM1_5 number(20,8), SEQ_PARAM2 number(20,8), SEQ_PARAM2_2 number(20,8), SEQ_PARAM2_3 number(20,8), SEQ_PARAM2_4 number(20,8), SEQ_PARAM2_5 number(20,8), SEQ_PARAM3 number(20,8), SEQ_PARAM3_2 number(20,8),
      SEQ_PARAM3_3 number(20,8), SEQ_PARAM3_4 number(20,8), SEQ_PARAM3_5 number(20,8), SOURCE number(10,0), SPATIAL_INDEX_100 number(12,0), SPATIAL_INDEX_200 number(12,0), SPATIAL_INDEX_25 number(12,0), SPATIAL_INDEX_400 number(12,0), SPATIAL_INDEX_50 number(12,0), TB_POINT_NUMBER number(15,0), TD_DA number(10,0), TD_GROUP number(10,0), TD_LAYER number(10,0), TD_NUMBER varchar2(50), TD_POINT_NUMBER number(10,0), USER_CREATED varchar2(255), USER_DELETED varchar2(255), USER_MODIFIED varchar2(255), X1 number(20,8), X2 number(20,8), X3 number(20,8), X4 number(20,8), X5 number(20,8), Y1 number(20,8), Y2 number(20,8), Y3 number(20,8), Y4 number(20,8), Y5 number(20,8), Z1 number(20,8), Z2 number(20,8),
      Z3 number(20,8), Z4 number(20,8), Z5 number(20,8), Z_DIFF number(20,8), Z_TERRAIN number(20,8)
    -> ouvrage_pos_exacte_depuis_250
ouvrage_pos_exacte_depuis_250: ouvrage pos exacte depuis 250
    GeometryExtractor_OUTPUT_16 -> FeatureMerger_3 [input 2]
FeatureMerger_3
    REFEEATTR = GID
    MERGE_TYPE = Attributes and Geometry - Build Aggregates
    PROCESS_DUPS = No
    BUILD_INCOMPLETE = No
    REFERATTR = GID
    COMPLETE -> FeatureMerger [input 2]
Note: postgres - install type
distribution.installation_type (reader POSTGRES_2)
    attributes: id serial,PRIKEY, shortname varchar(5), name varchar(30),PRIKEY, schema_view bool
    -> installation_type [input 1]
installation_type: installation type
    FeatureMerger_2_COMPLETE_33 -> FeatureMerger [input 1]
FeatureMerger
    REFEEATTR = OUVRAGE
    MERGE_TYPE = Geometry - Build Aggregates
    PROCESS_DUPS = No
    BUILD_INCOMPLETE = No
    REFERATTR = id
    COMPLETE -> distribution.installation (writer POSTGIS_1)
distribution.installation (writer POSTGIS_1)
    attributes: eca text, id int4, id_distributor varchar(30), id_status text, id_type int4, name varchar(30), open_water_surface text, parcel text, remarks text, identification text, year text
SIGE_DISTRIBUTION_SCHEMA.WA_BAUWERK_GEO (reader ORACLE8I_DB_1)
    attributes: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

FME custom transformer year

AttributeFilter_2_INPUT_11 (input)
    -> AttributeFilter_2
Note: Selectionne les dates nulles ou 0
AttributeFilter_2
    ATTR_NAME = year
    ATTR_VALUES = 0
    0 -> AttributeSetter
    <BLANK> -> AttributeSetter
    <UNFILTERED> -> NullAttributeReplacer
Note: Changer les dates a 1899
AttributeSetter
    VAL = 1899
    DEST_ATTR = year
    -> AttributeCreator
Note: Remplace les dates null a 1899
NullAttributeReplacer
    NEW_VALUE = 1899
    SRC_ATTRS = year
    -> AttributeCreator
Note: Creation des attributs manquants
AttributeCreator
    ATTR_LIST = id_parent,NULL,schema_force_view,NULL
    -> AttributeCreator_OUTPUT_9 (output)
AttributeCreator_OUTPUT_9 (output)

FME custom transformer ouvrage pos exacte depuis 250

StringFormatter_INPUT_5 (input)
    -> StringFormatter
StringFormatter
    FORMAT = .10f
    SRC_ATTRS = X1,Y1
    -> StringConcatenator
StringConcatenator
    PARM_LINE = POINT(,&Y1, ,&X1, )
    VAL_ATTR = WKT
    -> GeometryReplacer
GeometryReplacer
    KIND_LONG = OGC Well Known Text
    ATTR = WKT
    -> GeometryOGCValidator
GeometryOGCValidator
    VALIDATION_TYPE = Simple
    PASSED -> CoordinateSystemSetter
CoordinateSystemSetter
    COORDSYS = EPSG:21781
    -> GeometryExtractor
GeometryExtractor
    KIND_LONG = OGC Well Known Binary
    ATTR = geometry
    OGCVERSION = 1.1
    -> GeometryExtractor_OUTPUT_16 (output)
GeometryExtractor_OUTPUT_16 (output)

FME custom transformer installation type

AttributeRenamer_2_INPUT_37 (input)
    -> AttributeRenamer_2
AttributeRenamer_2
    ATTR_LIST = id_type,id
    -> AttributeRemover
AttributeRemover
    REMOVE_ATTRS = type
    -> FeatureMerger_2 [input 2]
FeatureMerger_2_REQUESTOR_33 (input)
    -> FeatureMerger_2 [input 1]
FeatureMerger_2
    REFEEATTR = shortname
    MERGE_TYPE = Attributes Only
    PROCESS_DUPS = No
    BUILD_INCOMPLETE = No
    REFERATTR = BAUWERK_TYP
    COMPLETE -> FeatureMerger_2_COMPLETE_33 (output)
FeatureMerger_2_COMPLETE_33 (output)
