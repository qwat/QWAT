FME workspace oracle2postgres_7_valve_202.fmw

Parameters:
- SourceDataset_ORACLE8I_DB = orcl   # Source Oracle Non-spatial Service
- DestDataset_POSTGIS = sige   # Destination PostGIS Dataset

Readers:
- ORACLE8I_DB_1: ORACLE8I_DB from $(SourceDataset_ORACLE8I_DB) in EPSG:21781

Writers:
- POSTGIS_1: POSTGIS to $(DestDataset_POSTGIS) in EPSG:21781

SIGE_DISTRIBUTION.WA_SCHIEBER (reader ORACLE8I_DB_1)
    attributes: ALTITUDE number(5,1), ANSCHLUSS_ABSAUGUNG number(1,0), ANSCHLUSS_SPERRSTOFFE number(1,0), ANTRIEBS_ART varchar2(5), AREA_NOMINAL number(20,8), ARTIKEL_NR varchar2(50), BEMERKUNG varchar2(255), BESCHICHTUNG_AUSSEN varchar2(5), BESCHICHTUNG_INNEN varchar2(5), BEZEICHNUNG varchar2(20), BEZEICHNUNG2 varchar2(20), DATENUEBERTRAGUNG number(20,0), DATUM_VERGABE date, DELETED number(1,0), DRUCKZONE_ID number(20,0), ECKFORM number(1,0), EIGENTUMSVERHAELTNIS varchar2(5), EINBAUFIRMA_ID number(10,0), EINBAUJAHR number(20,0), F1 varchar2(20), F2 varchar2(20), F3 varchar2(20), FERME number(1,0), FESTSTELLBAR number(1,0), FID number(10,0), FID_LAGEBEZEICHNUNG number(10,0), FID_NETZPUNKT number(10,0), FLST_KENNZEICHEN_OF varchar2(25), FLST_NENNER number(20,0), FLST_NR number(20,0),
      FLST_ZAEHLER number(20,0), FREMDANTRIEB number(20,0), FUNKTION varchar2(5), GAUCHE number(1,0), GEMARKUNG number(20,0), GID number(10,0), HAUSNUMMER number(10,0), HAUSNUMMER_ERG varchar2(25), HERSTELLER_ID number(20,0), ID_BESCHILDERUNG number(10,0), KATASTERBLATT varchar2(5), LAGEGENAUIGKEIT varchar2(5), MATERIAL varchar2(5), NAME varchar2(60), NAME2 varchar2(50), NENNDRUCK number(20,5), NENNWEITE varchar2(15), ORTSBEZEICHNUNG varchar2(50), POINT_NUMBER varchar2(50), SCHIEBER_ART varchar2(5), SCHIEBER_AUF number(1,0), SCHILD_MONTIERT varchar2(2), SKALIERFAKTOR number(20,5), STANDORT varchar2(255), STATUS varchar2(5), STETIGES_STELLVERHALTEN number(1,0), STRANG_ID number(10,0), TB_POINT_NUMBER number(15,0), UE_PLAN_NUMMER varchar2(7), VERBINDUNGSART varchar2(15),
      V_COMMUNE number(10,0), WERKPLAN_NUMMER varchar2(7), ZERTIFIKAT varchar2(10)
    -> AttributeFilter
AttributeFilter
    ATTR_NAME = DELETED
    ATTR_VALUES = 0
    0 -> AttributeRenamer
AttributeRenamer
    ATTR_LIST = id,FID,remark,BEMERKUNG,year,EINBAUJAHR,diameter_nominal,NENNWEITE,closed,FERME,identification,POINT_NUMBER
    -> NullAttributeReplacer
Note: années
NullAttributeReplacer
    NEW_VALUE = 1899
    SRC_ATTRS = year
    -> AttributeCreator
Note: precision
AttributeCreator
    ATTR_LIST = id_precision,1105,id_precisionalti,1126
    -> AttributeValueMapper
Note: closed checkbox
AttributeValueMapper
    LUT = 1,False,-1,True,,False
    SRC = closed
    VAL_ATTR = closed
    DIRECTION = Forward
    -> AttributeValueMapper_2
Note: type
AttributeValueMapper_2
    LUT = VG,6301,CL,6302,VAN,6303,I,6304,J,6305,LD,6306,PU,6307,SA,6308,SP,6309,V,6310,P,6311,E,6312,A,6313,TEL,634,,6304
    SRC = SCHIEBER_ART
    VAL_ATTR = id_type
    DIRECTION = Forward
    -> AttributeValueMapper_3
Note: function
AttributeValueMapper_3
    LUT = REG,6101,VE,6102,VBP,6103,OUV,6104,OA,6105,SEC,6106,VIN,6107,VH,6108,I,6109,VID,6110,VR,6111,VIVE,6112,CLAP,6113,,
    SRC = FUNKTION
    VAL_ATTR = id_function
    DIRECTION = Forward
    -> FeatureMerger [input 1]
SIGE_DISTRIBUTION.WA_SCHIEBER_GEO (reader ORACLE8I_DB_1)
    attributes: ACCURACY_LEVEL number(20,8), AREA number(20,8), AVG_DEV_XY number(20,8), AVG_DEV_Z number(20,8), AZIMUTH number(20,8), CALC_CODE number(4,0), CALC_NUMBER number(10,0), CLIPPING number(1,0), CREATION_CODE_XY_1 number(4,0), CREATION_CODE_XY_2 number(4,0), CREATION_CODE_XY_3 number(4,0), CREATION_CODE_XY_4 number(4,0), CREATION_CODE_XY_5 number(4,0), CREATION_CODE_Z number(4,0), DA number(10,0), DATE_CREATED date, DATE_DELETED date, DATE_MODIFIED date, DELETED number(1,0), DIM_X number(20,8), DIM_Y number(20,8), DTEXT number(1,0), ESEQ number(10,0), ETYPE number(4,0), FID number(10,0), FIELD_CODE number(4,0), FRAME number(1,0), GEO_CONSTRAINT number(1,0), GID number(10,0), ID number(10,0),
      INVISIBLE number(1,0), LABEL_FROM number(10,0), LABEL_TEXT varchar2(2000), LABEL_TO number(10,0), LINEATTRIBUTE_ID number(10,0), MUTATION_ID_CREATED number(10,0), MUTATION_ID_DELETED number(10,0), MUTATION_ID_MODIFIED number(10,0), MUTATION_STATUS_CREATED number(10,0), MUTATION_STATUS_DELETED number(10,0), M_DIRECTION number(20,8), M_DISTANCE number(20,8), ORIENTATION number(20,8), ORIGIN number(4,0), PERIMETER number(20,8), QUALITY number(10,0), SEQ number(10,0), SEQ_ETYPE number(4,0), SEQ_PARAM1 number(20,8), SEQ_PARAM1_2 number(20,8), SEQ_PARAM1_3 number(20,8), SEQ_PARAM1_4 number(20,8), SEQ_PARAM1_5 number(20,8), SEQ_PARAM2 number(20,8), SEQ_PARAM2_2 number(20,8), SEQ_PARAM2_3 number(20,8), SEQ_PARAM2_4 number(20,8), SEQ_PARAM2_5 number(20,8), SEQ_PARAM3 number(20,8), SEQ_PARAM3_2 number(20,8),
      SEQ_PARAM3_3 number(20,8), SEQ_PARAM3_4 number(20,8), SEQ_PARAM3_5 number(20,8), SOURCE number(10,0), SPATIAL_INDEX_100 number(12,0), SPATIAL_INDEX_200 number(12,0), SPATIAL_INDEX_25 number(12,0), SPATIAL_INDEX_400 number(12,0), SPATIAL_INDEX_50 number(12,0), TB_POINT_NUMBER number(15,0), TD_DA number(10,0), TD_GROUP number(10,0), TD_LAYER number(10,0), TD_NUMBER varchar2(50), TD_POINT_NUMBER number(10,0), USER_CREATED varchar2(255), USER_DELETED varchar2(255), USER_MODIFIED varchar2(255), X1 number(20,8), X2 number(20,8), X3 number(20,8), X4 number(20,8), X5 number(20,8), Y1 number(20,8), Y2 number(20,8), Y3 number(20,8), Y4 number(20,8), Y5 number(20,8), Z1 number(20,8), Z2 number(20,8),
      Z3 number(20,8), Z4 number(20,8), Z5 number(20,8), Z_DIFF number(20,8), Z_TERRAIN number(20,8)
    -> StringFormatter
StringFormatter
    FORMAT = .10f
    SRC_ATTRS = X1,Y1
    -> StringConcatenator
StringConcatenator
    PARM_LINE = POINT(,&Y1, ,&X1, )
    VAL_ATTR = WKT
    -> GeometryReplacer
GeometryReplacer
    KIND_LONG = OGC Well Known Text
    ATTR = WKT
    -> GeometryOGCValidator
GeometryOGCValidator
    VALIDATION_TYPE = Simple
    PASSED -> CoordinateSystemSetter
CoordinateSystemSetter
    COORDSYS = EPSG:21781
    -> GeometryExtractor
GeometryExtractor
    KIND_LONG = OGC Well Known Binary
    ATTR = geometry
    OGCVERSION = 1.1
    -> FeatureMerger [input 2]
FeatureMerger
    REFEEATTR = GID
    MERGE_TYPE = Geometry - Build Aggregates
    PROCESS_DUPS = No
    BUILD_INCOMPLETE = No
    REFERATTR = GID
    COMPLETE -> distribution.od_valve (writer POSTGIS_1)
distribution.od_valve (writer POSTGIS_1)
    attributes: id int4, closed varchar(30), remark text, year int4, identification int4, id_type int4, id_function int4, id_precision int4
