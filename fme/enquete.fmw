FME workspace enquete.fmw

Parameters:
- SourceDataset_ACAD = F:\fme\input\Calque_enquetes.dwg   # Source Autodesk AutoCAD DWG/DXF File(s)
- DestDataset_POSTGIS = sige   # Destination PostGIS Dataset

Readers:
- ACAD_1: ACAD from $(SourceDataset_ACAD) in EPSG:21781

Writers:
- POSTGIS_1: POSTGIS to $(DestDataset_POSTGIS) in EPSG:21781

0 (reader ACAD_1)
    -> 2DForcer
canal-du-Haut-Lac-projete @ 1 (reader ACAD_1)
    -> 2DForcer
EP_CONTOUR (reader ACAD_1)
    -> 2DForcer
canal-du-Haut-Lac-projete @ 0.5 (reader ACAD_1)
    -> 2DForcer
canal-du-Haut-Lac-projete (reader ACAD_1)
    -> 2DForcer
canal-du-Haut-Lac-projete @ 2.5 (reader ACAD_1)
    -> 2DForcer
canal-du-Haut-Lac-projete @ 0.2 (reader ACAD_1)
    -> 2DForcer
EP_ENQUETE (reader ACAD_1)
    -> 2DForcer
2DForcer
    2D -> GeometryFilter
GeometryFilter
    BREAK_AGG = No
    LINE -> ArcStroker
    POINT -> AttributeFilter
    TEXT -> AttributeFilter
    RASTER -> AttributeFilter
    SURFACE -> AttributeFilter
    SOLID -> AttributeFilter
    COLLECTION -> AttributeFilter
    NULL -> AttributeFilter
    ARC -> ArcStroker_2
    AREA -> Deaggregator
    ELLIPSE -> Deaggregator
ArcStroker_2
    STROKE_CHOICE = Number of Interpolated Edges
    NUM = 0
    MAKE_POLY = No
    STROKED -> ArcStroker
ArcStroker
    STROKE_CHOICE = Number of Interpolated Edges
    NUM = 0
    MAKE_POLY = Yes
    STROKED -> GeometryCoercer
GeometryCoercer
    KIND = fme_line
    COERCED -> GeometryExtractor
GeometryExtractor
    KIND_LONG = OGC Well Known Text
    ATTR = _geometry
    OGCVERSION = 1.1
    -> GeometryRemover
GeometryRemover
    -> GeometryReplacer
GeometryReplacer
    KIND_LONG = OGC Well Known Text
    ATTR = _geometry
    -> sige_commun.enquete_ligne (writer POSTGIS_1)
sige_commun.enquete_ligne (writer POSTGIS_1)
Deaggregator
    PART_NUMBER_FIELD = _part_number
    RECURSIVE = Yes
    SPLIT_COMPOSITES = No
    GEOM_NAME_FIELD = _geometry_name
    DEAGGREGATED -> GeometryCoercer_2
GeometryCoercer_2
    CHECKZ = No
    KIND = fme_polygon
    COERCED -> GeometryExtractor_2
GeometryExtractor_2
    KIND_LONG = OGC Well Known Text
    ATTR = _geometry
    OGCVERSION = 1.1
    -> GeometryRemover_2
GeometryRemover_2
    -> GeometryReplacer_2
GeometryReplacer_2
    KIND_LONG = OGC Well Known Text
    ATTR = _geometry
    -> sige_commun.enquete_polygone (writer POSTGIS_1)
sige_commun.enquete_polygone (writer POSTGIS_1)
AttributeFilter
    ATTR_NAME = fme_text_size
    ATTR_VALUES = 5

FME custom transformer liner

AttributeRemover_2_INPUT_39 (input)
    -> AttributeRemover_2
Note: Champs inutiles
AttributeRemover_2
    REMOVE_ATTRS = ACCURACY_LEVEL,AREA,AVG_DEV_XY,AVG_DEV_Z,AZIMUTH,CALC_CODE,CALC_NUMBER,CLIPPING,CREATION_CODE_XY_1,CREATION_CODE_XY_2,CREATION_CODE_XY_3,CREATION_CODE_XY_4,CREATION_CODE_XY_5,CREATION_CODE_Z,DA,DATE_CREATED,DATE_DELETED,DATE_MODIFIED,DELETED,DIM_X,DIM_Y,DTEXT,ESEQ,ETYPE,FID,FIELD_CODE,FRAME,GEO_CONSTRAINT,ID,INVISIBLE,LABEL_FROM,LABEL_TEXT,LABEL_TO,LINEATTRIBUTE_ID,MUTATION_ID_CREATED,MUTATION_ID_DELETED,MUTATION_ID_MODIFIED,MUTATION_STATUS_CREATED,MUTATION_STATUS_DELETED,M_DIRECTION,M_DISTANCE,ORIENTATION,ORIGIN,PERIMETER,QUALITY,SEQ_ETYPE,SEQ_PARAM1,SEQ_PARAM1_2,SEQ_PARAM1_3,SEQ_PARAM1_4,SEQ_PARAM1_5,SEQ_PARAM2,SEQ_PARAM2_2,SEQ_PARAM2_3,SEQ_PARAM2_4,SEQ_PARAM2_5,SEQ_PARAM3,SEQ_PARAM3_2,SEQ_PARAM3_3,SEQ_PARAM3_4,SEQ_PARAM3_5,SOURCE,SPATIAL_INDEX_100,SPATIAL_INDEX_200,SPATIAL_INDEX_25,SPATIAL_INDEX_400,SPATIAL_INDEX_50,TB_POINT_NUMBER,TD_DA,TD_GROUP,TD_LAYER,TD_NUMBER,TD_POINT_NUMBER,USER_CREATED,USER_DELETED,USER_MODIFIED,X2,X3,X4,X5,Y2,Y3,Y4,Y5,Z1,Z2,Z3,Z4,Z5,Z_DIFF,Z_TERRAIN
    -> Sorter
Note: Tri par GID puis par SEQ
Sorter
    SORT_PARM = GID NUMERIC ASCENDING SEQ NUMERIC ASCENDING
    SORTED -> StringFormatter
Note: Transforme les coordonnées en texte
StringFormatter
    FORMAT = .4f
    SRC_ATTRS = X1,Y1
    -> StringConcatenator_2
Note: Concatene X et Y dans xy
StringConcatenator_2
    PARM_LINE = &Y1, ,&X1
    VAL_ATTR = xy
    -> AttributeRemover_3
Note: Suppression X et Y
AttributeRemover_3
    REMOVE_ATTRS = X1,Y1
    -> ListBuilder
Note: Grouper les éléments par GID (triés en SEQ)
ListBuilder
    LIST_NAME = list
    -> ListConcatenator
Note: Concatene les xy des memes conduites
ListConcatenator
    SEP = ", "
    VAL_ATTR = _linestring
    LIST_ATTR = list{}.xy
    -> AttributeCreator_2
Note: Ajout des champs gauche et droite du WKT
AttributeCreator_2
    ATTR_LIST = left,LINESTRING(,right,)
    -> StringConcatenator_3
Note: Concatene avec les parenthèses
StringConcatenator_3
    PARM_LINE = &left,&_linestring,&right
    VAL_ATTR = linestring
    -> AttributeRemover_4
Note: Suppression des champs intermediaires
AttributeRemover_4
    REMOVE_ATTRS = _linestring,left,right
    -> GeometryReplacer
Note: Create GEOM from WKT
GeometryReplacer
    KIND_LONG = OGC Well Known Text
    ATTR = linestring
    -> GeometryOGCValidator
GeometryOGCValidator
    VALIDATION_TYPE = Valid
    PASSED -> CoordinateSystemSetter
CoordinateSystemSetter
    COORDSYS = EPSG:21781
    -> GeometryExtractor
Note: Write WKB from GEOM
GeometryExtractor
    KIND_LONG = OGC Well Known Binary
    ATTR = wkb_geometry
    OGCVERSION = 1.1
    -> AttributeRemover_4_OUTPUT_86 (output)
AttributeRemover_4_OUTPUT_86 (output)
