FME workspace oracle2postgres_8_leak_202.fmw

Parameters:
- DestDataset_POSTGIS = sige   # Destination PostGIS Dataset
- SourceDataset_ORACLE8I_DB = orcl   # Source Oracle Non-spatial Service
- SourceDataset_ORACLE8I_DB_4 = orcl   # Source Oracle Non-spatial Service

Readers:
- ORACLE8I_DB_1: ORACLE8I_DB from $(SourceDataset_ORACLE8I_DB)
- ORACLE8I_DB_2: ORACLE8I_DB from $(SourceDataset_ORACLE8I_DB_4)

Writers:
- POSTGIS_1: POSTGIS to $(DestDataset_POSTGIS) in EPSG:21781

SIGE_DISTRIBUTION.WA_STOERUNG_STRANG (reader ORACLE8I_DB_1)
    attributes: AREA_NOMINAL number(20,8), AUFTRAG_ID number(20,0), BEMERKUNG varchar2(255), BEZEICHNUNG1 varchar2(20), BEZEICHNUNG2 varchar2(20), COMMUNE number(10,0), CONDUITE_REMPLACEE varchar2(20), DELETED number(1,0), DESCRIPTION varchar2(255), F1 varchar2(20), F2 varchar2(20), F3 varchar2(20), FID number(10,0), FID_LAGEBEZEICHNUNG number(10,0), FREMDSCHADEN number(10,0), FUITES_FUI_ADRESSE varchar2(255), FUITES_FUI_ANNÉE number(10,0), FUITES_FUI_DIAM_CANAL varchar2(255), FUITES_FUI_MAT_CANAL varchar2(255), FUITES_FUI_TYPE_CANAL varchar2(255), GID number(10,0), ID_SCHADENBEHEBUNG number(10,0), NUMMER number(10,0), POINT_NUMBER varchar2(50), PRUEFER_ID number(20,0), REPARATURMATERIAL varchar2(80), SCHADENSTELLE varchar2(100), SKALIERFAKTOR number(20,5), STOERUNG varchar2(50), STOERUNGSART varchar2(5),
      STOERUNGSDATUM date, STOERUNGSURSACHE varchar2(5), STOERUNG_BEHOBEN number(20,0), STOERUNG_BEHOBEN_AM date, STRANG_ID number(20,0), TB_POINT_NUMBER number(15,0)
    -> AttributeFilter
Note: deleted
AttributeFilter
    ATTR_NAME = DELETED
    ATTR_VALUES = 0
    0 -> StringConcatenator_2
Note: description
StringConcatenator_2
    PARM_LINE = &DESCRIPTION, ,&BEMERKUNG
    VAL_ATTR = description
    -> StringConcatenator_3
Note: address
StringConcatenator_3
    PARM_LINE = &SCHADENSTELLE, ,&FUITES_FUI_ADRESSE
    VAL_ATTR = address
    -> AttributeRenamer
AttributeRenamer
    ATTR_LIST = id,FID,repair,REPARATURMATERIAL,detection_date,STOERUNGSDATUM,repair_date,STOERUNG_BEHOBEN_AM,pipe_replaced,CONDUITE_REMPLACEE
    -> AttributeValueMapper_2
Note: type
AttributeValueMapper_2
    LUT = CF,9141,CL,9142,CA,9143,TC,9144,DEF,9145,,9145
    SRC = STOERUNGSART
    VAL_ATTR = id_type
    DIRECTION = Forward
    -> AttributeValueMapper_3
Note: cause
AttributeValueMapper_3
    LUT = C,9101,M,9102,F,9103,P,9104,S,9105,,NULL
    SRC = STOERUNGSURSACHE
    VAL_ATTR = id_cause
    DIRECTION = Forward
    -> AttributeValueMapper_4
Note: dommage
AttributeValueMapper_4
    LUT = 2,9124,3,9123,4,9122,5,9123,6,9121,,9123
    SRC = ID_SCHADENBEHEBUNG
    VAL_ATTR = id_damage
    DIRECTION = Forward
    -> FeatureMerger [input 1]
SIGE_DISTRIBUTION.WA_STOERUNG_STRANG_GEO (reader ORACLE8I_DB_2)
    attributes: ACCURACY_LEVEL number(20,8), AREA number(20,8), AVG_DEV_XY number(20,8), AVG_DEV_Z number(20,8), AZIMUTH number(20,8), CALC_CODE number(4,0), CALC_NUMBER number(10,0), CLIPPING number(1,0), CREATION_CODE_XY_1 number(4,0), CREATION_CODE_XY_2 number(4,0), CREATION_CODE_XY_3 number(4,0), CREATION_CODE_XY_4 number(4,0), CREATION_CODE_XY_5 number(4,0), CREATION_CODE_Z number(4,0), DA number(10,0), DATE_CREATED date, DATE_DELETED date, DATE_MODIFIED date, DELETED number(1,0), DIM_X number(20,8), DIM_Y number(20,8), DTEXT number(1,0), ESEQ number(10,0), ETYPE number(4,0), FID number(10,0), FIELD_CODE number(4,0), FRAME number(1,0), GEO_CONSTRAINT number(1,0), GID number(10,0), ID number(10,0),
      INVISIBLE number(1,0), LABEL_FROM number(10,0), LABEL_TEXT varchar2(2000), LABEL_TO number(10,0), LINEATTRIBUTE_ID number(10,0), MUTATION_ID_CREATED number(10,0), MUTATION_ID_DELETED number(10,0), MUTATION_ID_MODIFIED number(10,0), MUTATION_STATUS_CREATED number(10,0), MUTATION_STATUS_DELETED number(10,0), M_DIRECTION number(20,8), M_DISTANCE number(20,8), ORIENTATION number(20,8), ORIGIN number(4,0), PERIMETER number(20,8), QUALITY number(10,0), SEQ number(10,0), SEQ_ETYPE number(4,0), SEQ_PARAM1 number(20,8), SEQ_PARAM1_2 number(20,8), SEQ_PARAM1_3 number(20,8), SEQ_PARAM1_4 number(20,8), SEQ_PARAM1_5 number(20,8), SEQ_PARAM2 number(20,8), SEQ_PARAM2_2 number(20,8), SEQ_PARAM2_3 number(20,8), SEQ_PARAM2_4 number(20,8), SEQ_PARAM2_5 number(20,8), SEQ_PARAM3 number(20,8), SEQ_PARAM3_2 number(20,8),
      SEQ_PARAM3_3 number(20,8), SEQ_PARAM3_4 number(20,8), SEQ_PARAM3_5 number(20,8), SOURCE number(10,0), SPATIAL_INDEX_100 number(12,0), SPATIAL_INDEX_200 number(12,0), SPATIAL_INDEX_25 number(12,0), SPATIAL_INDEX_400 number(12,0), SPATIAL_INDEX_50 number(12,0), TB_POINT_NUMBER number(15,0), TD_DA number(10,0), TD_GROUP number(10,0), TD_LAYER number(10,0), TD_NUMBER varchar2(50), TD_POINT_NUMBER number(10,0), USER_CREATED varchar2(255), USER_DELETED varchar2(255), USER_MODIFIED varchar2(255), X1 number(20,8), X2 number(20,8), X3 number(20,8), X4 number(20,8), X5 number(20,8), Y1 number(20,8), Y2 number(20,8), Y3 number(20,8), Y4 number(20,8), Y5 number(20,8), Z1 number(20,8), Z2 number(20,8),
      Z3 number(20,8), Z4 number(20,8), Z5 number(20,8), Z_DIFF number(20,8), Z_TERRAIN number(20,8)
    -> StringFormatter
StringFormatter
    FORMAT = .10f
    SRC_ATTRS = X1,Y1
    -> StringConcatenator
StringConcatenator
    PARM_LINE = POINT(,&Y1, ,&X1, )
    VAL_ATTR = WKT
    -> GeometryReplacer
GeometryReplacer
    KIND_LONG = OGC Well Known Text
    ATTR = WKT
    -> GeometryOGCValidator
GeometryOGCValidator
    VALIDATION_TYPE = Simple
    PASSED -> CoordinateSystemSetter
CoordinateSystemSetter
    COORDSYS = EPSG:21781
    -> GeometryExtractor
GeometryExtractor
    KIND_LONG = OGC Well Known Binary
    ATTR = geometry
    OGCVERSION = 1.1
    -> FeatureMerger [input 2]
FeatureMerger
    REFEEATTR = GID
    MERGE_TYPE = Geometry - Build Aggregates
    PROCESS_DUPS = No
    BUILD_INCOMPLETE = No
    REFERATTR = GID
    COMPLETE -> distribution.od_leak (writer POSTGIS_1)
distribution.od_leak (writer POSTGIS_1)
    attributes: id int4, id_type int4, id_cause int4, id_damage int4, detection_date date, repair_date date, address text, pipe_replaced bool, description text, repair text
