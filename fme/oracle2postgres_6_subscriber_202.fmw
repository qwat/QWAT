FME workspace oracle2postgres_6_subscriber_202.fmw

Parameters:
- SourceDataset_ORACLE8I_DB = orcl   # Source Oracle Non-spatial Service
- DestDataset_POSTGIS = sige   # Destination PostGIS Dataset
- SourceDataset_ORACLE8I_DB_5 = orcl   # Source Oracle Non-spatial Service
- SourceDataset_ORACLE8I_DB_4 = orcl   # Source Oracle Non-spatial Service
- SourceDataset_POSTGRES = sige   # Source PostgreSQL Dataset

Readers:
- ORACLE8I_DB_1: ORACLE8I_DB from $(SourceDataset_ORACLE8I_DB)
- ORACLE8I_DB_2: ORACLE8I_DB from $(SourceDataset_ORACLE8I_DB_5)
- ORACLE8I_DB_3: ORACLE8I_DB from $(SourceDataset_ORACLE8I_DB_4)
- POSTGRES_1: POSTGRES from $(SourceDataset_POSTGRES)

Writers:
- POSTGIS_1: POSTGIS to $(DestDataset_POSTGIS) in EPSG:21781

SIGE_DISTRIBUTION.WA_GEBEINFUEHR (reader ORACLE8I_DB_1)
    attributes: AREA_NOMINAL number(20,8), ARTIKEL_NR varchar2(50), BEMERKUNG varchar2(255), BEZEICHNUNG varchar2(20), COMMUNE_PROV number(10,0), DELETED number(1,0), DRUCKZONE_ID number(10,0), EIGENTUMSVERHAELTNIS varchar2(5), EINBAUJAHR number(20,0), F1 varchar2(20), F2 varchar2(20), F3 varchar2(20), FACTEUR_ECHELLE number(2,1), FID number(10,0), FID_KUNDE number(10,0), FID_LAGEBEZEICHNUNG number(10,0), FID_NETZPUNKT number(10,0), FLST_KENNZEICHEN_OF varchar2(25), FLST_NENNER number(20,0), FLST_NR number(20,0), FLST_ZAEHLER number(20,0), FOLIO varchar2(15), GEMARKUNG number(20,0), GID number(10,0), HAUSNUMMER number(10,0), HAUSNUMMER_ERG varchar2(10), HERSTELLER_ID number(20,0), ISOLIERSTUECK_INTERN varchar2(15), KUNDENNUMMER varchar2(20), LAGEGENAUIGKEIT varchar2(5),
      NAME varchar2(60), NENNDRUCK number(20,5), NENNWEITE_EXTERN varchar2(15), NENNWEITE_INTERN varchar2(15), PARCELLE varchar2(10), PASTILLE number(1,0), POINT_NUMBER varchar2(50), SAMMELANSCHLUSS number(10,0), SPRINKLER_VORHANDEN number(20,0), STATUS varchar2(5), STRANG_ID number(10,0), TARIFNUMMER varchar2(10), TB_POINT_NUMBER number(15,0), TEXT varchar2(255), TOURNUMMER number(10,0), TYP varchar2(5), V_COMMUNE number(10,0)
    -> AttributeFilter
Note: supprimer DELETED
AttributeFilter
    ATTR_NAME = DELETED
    ATTR_VALUES = 0
    0 -> AttributeRemover
Note: enlever champs inutiles
AttributeRemover
    REMOVE_ATTRS = AREA_NOMINAL,ARTIKEL_NR,COMMUNE_PROV,DELETED,DRUCKZONE_ID,EIGENTUMSVERHAELTNIS,EINBAUJAHR,F1,F2,F3,FID_KUNDE,FID_LAGEBEZEICHNUNG,FID_NETZPUNKT,FLST_KENNZEICHEN_OF,FLST_NENNER,FLST_NR,FLST_ZAEHLER,FOLIO,GEMARKUNG,HAUSNUMMER,HAUSNUMMER_ERG,HERSTELLER_ID,ISOLIERSTUECK_INTERN,LAGEGENAUIGKEIT,NAME,NENNDRUCK,NENNWEITE_EXTERN,NENNWEITE_INTERN,POINT_NUMBER,SAMMELANSCHLUSS,SPRINKLER_VORHANDEN,STATUS,TARIFNUMMER,TB_POINT_NUMBER,TEXT,TOURNUMMER
    -> AttributeFilter_2
Note: Pastille: coché (= -1) = info bord de plan
AttributeFilter_2
    ATTR_NAME = PASTILLE
    ATTR_VALUES = 0,-1
    0 -> AttributeValueMapper
    <BLANK> -> AttributeValueMapper
Note: type
AttributeValueMapper
    LUT = ARR,9402,FONT,9403,WC,9404,SPK,9405,RES,6,,9401
    SRC = TYP
    VAL_ATTR = id_type
    DIRECTION = Forward
    -> AttributeRenamer
AttributeRenamer
    ATTR_LIST = id_pipe,STRANG_ID,identification,KUNDENNUMMER,parcel,PARCELLE,remark,BEMERKUNG
    -> AttributeRemover_2
AttributeRemover_2
    REMOVE_ATTRS = PASTILLE,TYP
    -> AttributeCreator
AttributeCreator
    ATTR_LIST = id_status,1301
    -> FeatureMerger [input 1]
SIGE_DISTRIBUTION.WA_GEBEINFUEHR_GEO (reader ORACLE8I_DB_2)
    attributes: ACCURACY_LEVEL number(20,8), AREA number(20,8), AVG_DEV_XY number(20,8), AVG_DEV_Z number(20,8), AZIMUTH number(20,8), CALC_CODE number(4,0), CALC_NUMBER number(10,0), CLIPPING number(1,0), CREATION_CODE_XY_1 number(4,0), CREATION_CODE_XY_2 number(4,0), CREATION_CODE_XY_3 number(4,0), CREATION_CODE_XY_4 number(4,0), CREATION_CODE_XY_5 number(4,0), CREATION_CODE_Z number(4,0), DA number(10,0), DATE_CREATED date, DATE_DELETED date, DATE_MODIFIED date, DELETED number(1,0), DIM_X number(20,8), DIM_Y number(20,8), DTEXT number(1,0), ESEQ number(10,0), ETYPE number(4,0), FID number(10,0), FIELD_CODE number(4,0), FRAME number(1,0), GEO_CONSTRAINT number(1,0), GID number(10,0), ID number(10,0),
      INVISIBLE number(1,0), LABEL_FROM number(10,0), LABEL_TEXT varchar2(2000), LABEL_TO number(10,0), LINEATTRIBUTE_ID number(10,0), MUTATION_ID_CREATED number(10,0), MUTATION_ID_DELETED number(10,0), MUTATION_ID_MODIFIED number(10,0), MUTATION_STATUS_CREATED number(10,0), MUTATION_STATUS_DELETED number(10,0), M_DIRECTION number(20,8), M_DISTANCE number(20,8), ORIENTATION number(20,8), ORIGIN number(4,0), PERIMETER number(20,8), QUALITY number(10,0), SEQ number(10,0), SEQ_ETYPE number(4,0), SEQ_PARAM1 number(20,8), SEQ_PARAM1_2 number(20,8), SEQ_PARAM1_3 number(20,8), SEQ_PARAM1_4 number(20,8), SEQ_PARAM1_5 number(20,8), SEQ_PARAM2 number(20,8), SEQ_PARAM2_2 number(20,8), SEQ_PARAM2_3 number(20,8), SEQ_PARAM2_4 number(20,8), SEQ_PARAM2_5 number(20,8), SEQ_PARAM3 number(20,8), SEQ_PARAM3_2 number(20,8),
      SEQ_PARAM3_3 number(20,8), SEQ_PARAM3_4 number(20,8), SEQ_PARAM3_5 number(20,8), SOURCE number(10,0), SPATIAL_INDEX_100 number(12,0), SPATIAL_INDEX_200 number(12,0), SPATIAL_INDEX_25 number(12,0), SPATIAL_INDEX_400 number(12,0), SPATIAL_INDEX_50 number(12,0), TB_POINT_NUMBER number(15,0), TD_DA number(10,0), TD_GROUP number(10,0), TD_LAYER number(10,0), TD_NUMBER varchar2(50), TD_POINT_NUMBER number(10,0), USER_CREATED varchar2(255), USER_DELETED varchar2(255), USER_MODIFIED varchar2(255), X1 number(20,8), X2 number(20,8), X3 number(20,8), X4 number(20,8), X5 number(20,8), Y1 number(20,8), Y2 number(20,8), Y3 number(20,8), Y4 number(20,8), Y5 number(20,8), Z1 number(20,8), Z2 number(20,8),
      Z3 number(20,8), Z4 number(20,8), Z5 number(20,8), Z_DIFF number(20,8), Z_TERRAIN number(20,8)
    -> AttributeRemover_3
AttributeRemover_3
    REMOVE_ATTRS = ACCURACY_LEVEL,AREA,AVG_DEV_XY,AVG_DEV_Z,AZIMUTH,CALC_CODE,CALC_NUMBER,CLIPPING,CREATION_CODE_XY_1,CREATION_CODE_XY_2,CREATION_CODE_XY_3,CREATION_CODE_XY_4,CREATION_CODE_XY_5,CREATION_CODE_Z,DA,DATE_CREATED,DATE_DELETED,DATE_MODIFIED,DELETED,DIM_X,DIM_Y,DTEXT,ESEQ,ETYPE,FIELD_CODE,FRAME,GEO_CONSTRAINT,ID,INVISIBLE,LABEL_FROM,LABEL_TEXT,LABEL_TO,LINEATTRIBUTE_ID,MUTATION_ID_CREATED,MUTATION_ID_DELETED,MUTATION_ID_MODIFIED,MUTATION_STATUS_CREATED,MUTATION_STATUS_DELETED,M_DIRECTION,M_DISTANCE,ORIENTATION,ORIGIN,PERIMETER,QUALITY,SEQ,SEQ_ETYPE,SEQ_PARAM1,SEQ_PARAM1_2,SEQ_PARAM1_3,SEQ_PARAM1_4,SEQ_PARAM1_5,SEQ_PARAM2,SEQ_PARAM2_2,SEQ_PARAM2_3,SEQ_PARAM2_4,SEQ_PARAM2_5,SEQ_PARAM3,SEQ_PARAM3_2,SEQ_PARAM3_3,SEQ_PARAM3_4,SEQ_PARAM3_5,SOURCE,SPATIAL_INDEX_100,SPATIAL_INDEX_200,SPATIAL_INDEX_25,SPATIAL_INDEX_400,SPATIAL_INDEX_50,TB_POINT_NUMBER,TD_DA,TD_GROUP,TD_LAYER,TD_NUMBER,TD_POINT_NUMBER,USER_CREATED,USER_DELETED,USER_MODIFIED,X2,X3,X4,X5,Y2,Y3,Y4,Y5,Z2,Z3,Z4,Z5,Z_DIFF,Z_TERRAIN
    -> StringFormatter
StringFormatter
    FORMAT = .10f
    SRC_ATTRS = X1,Y1
    -> StringConcatenator
StringConcatenator
    PARM_LINE = POINT(,&Y1, ,&X1, )
    VAL_ATTR = _concatenated
    -> GeometryReplacer
GeometryReplacer
    KIND_LONG = OGC Well Known Text
    ATTR = _concatenated
    -> GeometryOGCValidator
GeometryOGCValidator
    VALIDATION_TYPE = Simple
    PASSED -> CoordinateSystemSetter
CoordinateSystemSetter
    COORDSYS = EPSG:21781
    -> GeometryExtractor
GeometryExtractor
    KIND_LONG = OGC Well Known Binary
    ATTR = geometry
    OGCVERSION = 1.2
    -> FeatureMerger [input 2]
FeatureMerger
    GROUP_BY = GID
    REFEEATTR = GID
    MERGE_TYPE = Geometry - Build Aggregates
    PROCESS_DUPS = No
    BUILD_INCOMPLETE = No
    REFERATTR = GID
    COMPLETE -> FeatureMerger_2 [input 1]
Note: Communne 203
distribution.od_district (reader POSTGRES_1)
    attributes: id serial,PRIKEY, name varchar(40),PRIKEY, shortname varchar(12), zip varchar(12), land_registry varchar(12), subscriber_prefix varchar(12), colorcode int2, geometry char(5575944),GIST
    -> AttributeRenamer_2
AttributeRenamer_2
    ATTR_LIST = id_district,id
    -> FeatureMerger_3 [input 2]
Note: commune TB
SIGE_DISTRIBUTION.V_COMMUNES (reader ORACLE8I_DB_3)
    attributes: ABREGE varchar2(3), AREA_GERECHNET number(20,8), AREA_NOMINAL number(20,8), CANTON varchar2(2), DELETED number(1,0), FID number(10,0), GID number(10,0), INTITULE_LISTE varchar2(10), NOM varchar2(30), NO_RF number(3,0), NPA number(4,0), PREFIXE_ABT number(2,0), STATUT_ASSAIN varchar2(20), STATUT_DISTRIB varchar2(20)
    -> FeatureMerger_2 [input 2]
FeatureMerger_2
    REFEEATTR = FID
    MERGE_TYPE = Attributes Only
    PROCESS_DUPS = No
    BUILD_INCOMPLETE = No
    REFERATTR = V_COMMUNE
    COMPLETE -> FeatureMerger_3 [input 1]
    INCOMPLETE -> AttributeFilter_3
    EMPTY -> AttributeFilter_3
FeatureMerger_3
    REFEEATTR = name
    MERGE_TYPE = Attributes Only
    PROCESS_DUPS = No
    BUILD_INCOMPLETE = No
    REFERATTR = NOM
    COMPLETE -> AttributeFilter_3
Note: séparation compteur reseau
AttributeFilter_3
    ATTR_NAME = id_type
    ATTR_VALUES = 6
    <BLANK> -> distribution.od_subscriber (writer POSTGIS_1)
    6 -> distribution.od_meter (writer POSTGIS_1)
    <UNFILTERED> -> distribution.od_subscriber (writer POSTGIS_1)
distribution.od_subscriber (writer POSTGIS_1)
    attributes: id_type int8, id_pipe int8, parcel char(30), identification int8, remark text, id_district int4
distribution.od_meter (writer POSTGIS_1)
    attributes: id_pipe int8, parcel char(30), identification int8, remark text, id_district int4
Visualizer
